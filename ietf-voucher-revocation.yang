module ietf-voucher-revocation {
  yang-version 1.1;

  namespace
    "urn:ietf:params:xml:ns:yang:ietf-voucher-revocation";
  prefix "vr";

  import ietf-yang-types {
    prefix yang;
    reference "RFC 6991: Common YANG Data Types";
  }

  import ietf-restconf {
    prefix rc;
    description
      "This import statement is only present to access the yang-data
       extension defined in RFC 8040.  The yang-data extension doesn't
       itself have anything to do with RESTCONF, but was placed in the
       that RFC for convenience.  This extension is being tracked to
       be moved to the next version of the YANG modeling language.
       Regardless where or how this extension statement is defined,
       there should not be any impact to a voucher revocation's
       encoding.";
    reference "RFC 8040: RESTCONF Protocol";
  }

  organization
   "IETF ANIMA Working Group";

  contact
   "WG Web:   <http://tools.ietf.org/wg/anima/>
    WG List:  <mailto:anima@ietf.org>
    Author:   Kent Watsen
              <mailto:kwatsen@juniper.net>
    Author:   Max Pritikin
              <mailto:pritikin@cisco.com>
    Author:   Michael Richardson
              <mailto:mcr+ietf@sandelman.ca>";

  description
   "This module defines the format for a voucher revocation, which
    is produced by the pledge's manufacturer or delegate (MASA) to 
    indicate the revocation status of one or more vouchers.";

  revision "YYYY-MM-DD" {
    description
     "Initial version";
    reference
     "RFC XXXX: Voucher and Voucher Revocation Profiles
      for Bootstrapping Protocols";
  }

  rc:yang-data voucher-revocation-artifact {
    uses voucher-revocation-grouping;
  }

  grouping voucher-revocation-grouping {
    description
      "Grouping only exists for pyang tree output...";

    container voucher-revocation {
      config false;
      description
        "A voucher revocation that can provide the revocation
         status information for one or more pledges.";
  
      leaf revocation-type {
        type enumeration {
          enum issuer-wide {
            description
              "Indicates that this revocation spans all
               the vouchers under the issuer's scope.";
          }
          enum voucher-specific {
            description
              "Indicates that this revocation only regards
               a single voucher.";
          }
        }
        mandatory true;
        description
          "The revocation-type indicates if the revocation
           is issuer-wide (like a CRL) or voucher-specific
           (like an OCSP Response).  Both variations exist
           to enable implementations to choose between the
           number of revocation artifacts generated versus
           individual artifact size.";
      }
  
      leaf created-on {
        type yang:date-and-time;
        mandatory true;
        description
          "The date this voucher revocation was created";
      }
  
      leaf expires-on {
        type yang:date-and-time;
        description
          "An optional date value for when this voucher
           revocation expires.";
      }
  
      choice voucher-revocation-type {
        description
          "Identifies the revocation type as being either issuer-wide
           or voucher-specific.";
  
        container issuer-wide {
          description
            "This revocation provides issuer-wide revocation status
             (similar to a CRL).";
  
          container blacklist {
            description
              "Indicates that the list of vouchers have been
               revoked.  If a voucher is not listed, then it
               is considered good.";
            leaf-list voucher-identifier {
              type string;
              description
                "A fingerprint over the voucher artifact.";
            }
          }
        } // end issuer-wide
  
        container voucher-specific {
          description
            "This revocation provides voucher-specific revocation 
             status (similar to an OCSP response).";
  
          leaf voucher-identifier {
            type string;
            mandatory true;
            description
              "A fingerprint over the voucher artifact.";
          }
  
          leaf voucher-status {
            type enumeration {
              enum good {
                description
                  "Indicates that this voucher is valid";
              }
              enum revoked {
                description
                  "Indicates that this voucher is invalid";
              }
              enum unknown {
                description
                  "Indicates that the voucher's status is unknown";
              }
            } 
            mandatory true;
            description
              "Indicates if the revocation status for the specified
               voucher.";
          }
  
          container revocation-information {
            must "../voucher-status = 'revoked'";
  
            leaf revoked-on {
              type yang:date-and-time;
              mandatory true;
              description
                "The date this voucher was revoked";
            }
  
            leaf revocation-reason {  // remove, or add to
              type enumeration {      // issuer-wide also?
                enum unspecified {
                  description
                    "Indicates that the reason the voucher
                     was revoked is unspecified.";
                }
                enum key-compromise {
                  description
                    "Indicates that the reason the voucher
                     was revoked is because its key was
                     compromised.";
                }
                enum issuer-compromise {
                  description
                    "Indicates that the reason the voucher
                     was revoked is because its issuer was
                     compromised.";
                }
                enum affiliation-changed {
                  description
                    "Indicates that the reason the voucher
                     was revoked is because its affiliation
                     changed (e.g., pledge assigned to a
                     new owner.";
                }
                enum superseded {
                  description
                    "Indicates that the reason the voucher
                     was revoked is because it has been
                     superseded (e.g., the previous voucher
                     expired.";
                }
                enum cessation-of-operation {
                  description
                    "Indicates that the reason the voucher
                     was revoked is because its issuer has
                     ceased operations.";
                }
              }  // end enumeration
  
              mandatory true;
              description
                "modeled after 'CRLReason' in RFC 5280.";
            } // end revocation reason
  
            description
              "Provides details regarding why a voucher's revocation.
               Modeled after 'ResponseData' in RFC6960.";
  
          } // end revocation-information
        } // end voucher-specific
      } // end voucher-revocation-type
    } // end voucher-revocation
  } // end voucher-revocation-grouping

}
